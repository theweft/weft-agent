[DOCUMENT]
TITLE: weft-agent requirements
VERSION: 0.1 (draft)
OPTIONS:
  MARKUP: Text

[GRAMMAR]
ELEMENTS:
- TAG: SECTION
  PROPERTIES:
    IS_COMPOSITE: True
  FIELDS:
  - TITLE: UID
    TYPE: String
    REQUIRED: False
  - TITLE: TITLE
    TYPE: String
    REQUIRED: True
- TAG: TEXT
  FIELDS:
  - TITLE: UID
    TYPE: String
    REQUIRED: False
  - TITLE: STATEMENT
    TYPE: String
    REQUIRED: True
- TAG: REQUIREMENT
  FIELDS:
  - TITLE: UID
    TYPE: String
    REQUIRED: True
  - TITLE: STATUS
    TYPE: SingleChoice(Draft, Active, Deleted)
    REQUIRED: True
  - TITLE: VERIFICATION
    TYPE: SingleChoice(Test, Analysis, Inspection, Demonstration)
    REQUIRED: True
  - TITLE: TITLE
    TYPE: String
    REQUIRED: True
  - TITLE: STATEMENT
    TYPE: String
    REQUIRED: True
  - TITLE: RATIONALE
    TYPE: String
    REQUIRED: False
  - TITLE: SATISFIES
    HUMAN_TITLE: Satisfies (system requirements, weft-design)
    TYPE: String
    REQUIRED: False
  - TITLE: STANDARDS
    HUMAN_TITLE: Standards (draft mapping)
    TYPE: String
    REQUIRED: False
  - TITLE: FACTS
    HUMAN_TITLE: Facts (facts.toml in the design repository)
    TYPE: String
    REQUIRED: False
  RELATIONS:
  - TYPE: Parent
  - TYPE: File

[TEXT]
STATEMENT: >>>
Component requirements of weft-agent. Each is traced to implementing functions in crates/*/src and to tests in crates/*/tests by relation markers; the gate in crates/weft-agent/tests/requirements.rs fails when an Active requirement verified by Test lacks either. SATISFIES names the system requirements in weft-design/requirements/system.sdoc.
<<<

[[SECTION]]
TITLE: Document sync and decisions

[REQUIREMENT]
UID: AGT-001
STATUS: Active
VERIFICATION: Test
TITLE: Convergence over best-effort transport
STATEMENT: >>>
Nodes shall exchange documents by push and anti-entropy pull (summary, inventory, fetch) so that, once the network allows it, all honest nodes hold the same verified documents, despite loss, delay, reordering, duplicates and partitions.
<<<
RATIONALE: >>>
SYS-032 permits best-effort transports; correctness must not depend on transport guarantees.
<<<
SATISFIES: SYS-032, SYS-021

[REQUIREMENT]
UID: AGT-002
STATUS: Active
VERIFICATION: Test
TITLE: Content addressing
STATEMENT: >>>
Documents shall be stored by the SHA-256 of their bytes, the digest the verifier uses; a document arriving again over any path shall be dropped.
<<<
RATIONALE: >>>
Several uplinks and relays deliver the same document; deduplication needs no coordination.
<<<
SATISFIES: SYS-005, SYS-032

[REQUIREMENT]
UID: AGT-003
STATUS: Active
VERIFICATION: Test
TITLE: Only verified documents travel
STATEMENT: >>>
A node shall share (advertise, serve, forward) only documents its decider has verified. Intrinsically invalid documents (malformed, bad signature, wrong tenant) shall be quarantined for good; documents of unknown signers or without authorization shall stay local and pending until they verify.
<<<
RATIONALE: >>>
Otherwise any node could inject well-formed documents signed by arbitrary keys and the fleet would store and spread them forever (found by the simulation, 2026-10-20).
<<<
SATISFIES: SYS-021, SYS-016

[REQUIREMENT]
UID: AGT-004
STATUS: Active
VERIFICATION: Test
TITLE: Persist before acting
STATEMENT: >>>
The decider shall save the new verifier state before executing any instruction, and shall execute nothing if saving fails.
<<<
RATIONALE: >>>
Acting on a decision whose anti-rollback state was lost would allow rollback after a crash. AGT-010 makes the save itself durable.
<<<
SATISFIES: SYS-006

[REQUIREMENT]
UID: AGT-005
STATUS: Active
VERIFICATION: Test
TITLE: Path-independent decisions
STATEMENT: >>>
After convergence, every device's installed artifacts, applied configuration, conflicts and withheld components shall equal a fresh evaluation of the same documents, whatever path, order or relay delivered them.
<<<
RATIONALE: >>>
Same inputs, same decision (SYS-017); a malicious relay can only delay (SYS-021).
<<<
SATISFIES: SYS-017, SYS-021

[REQUIREMENT]
UID: AGT-006
STATUS: Active
VERIFICATION: Test
TITLE: Restart recovery
STATEMENT: >>>
A restarted node shall load its saved verifier state, refuse corrupt state, and recover missing documents from peers; until they are back, affected components are withheld.
<<<
RATIONALE: >>>
Restarts must never reset anti-rollback marks or act on incomplete information.
<<<
SATISFIES: SYS-006, SYS-013

[REQUIREMENT]
UID: AGT-007
STATUS: Active
VERIFICATION: Test
TITLE: Deterministic simulation
STATEMENT: >>>
The node runtime shall behave deterministically for the same inputs and timing, so that a simulation run can be replayed exactly from its seed.
<<<
RATIONALE: >>>
A failing seed in CI must be reproducible on any developer machine.
<<<

[REQUIREMENT]
UID: AGT-008
STATUS: Active
VERIFICATION: Test
TITLE: Bounded input from peers
STATEMENT: >>>
Everything a peer sends shall be bounded: document size, number of stored, pending and quarantined documents, and digests per message; malformed messages are dropped.
<<<
RATIONALE: >>>
Peers are untrusted.
<<<
SATISFIES: SYS-016

[REQUIREMENT]
UID: AGT-009
STATUS: Active
VERIFICATION: Test
TITLE: Portable topic keys
STATEMENT: >>>
Topic keys shall consist of segments of [a-z0-9_-], within the segment, depth and length limits, so that they are valid on every transport.
<<<
RATIONALE: >>>
Keys must map to MQTT, Zenoh and NATS without escaping.
<<<
SATISFIES: SYS-009
FACTS: pubsub.topic.segment_max, pubsub.topic.max_depth, pubsub.topic.max_len

[REQUIREMENT]
UID: AGT-010
STATUS: Active
VERIFICATION: Test
TITLE: Durable, atomic state file
STATEMENT: >>>
The decider's state shall be saved by writing a temporary file and syncing it, renaming it over the state file and syncing the directory, so that after a save returns the new state survives power loss and before it returns the previous one does. The file shall carry a checksum; a damaged file shall be refused, not loaded.
<<<
RATIONALE: >>>
docs/11. Tested with power cuts at every point of the save on turmoil's simulated filesystem; the same test fails for a protocol without fsync (300 of 300 runs lost an acknowledged state).
<<<
SATISFIES: SYS-006

[REQUIREMENT]
UID: AGT-011
STATUS: Active
VERIFICATION: Test
TITLE: Inbox directory
STATEMENT: >>>
The agent shall take documents from an inbox directory (for example a USB stick or files dropped by the adopter's own transport), reading it only, taking regular, non-hidden files up to the size limit, and treating every file as untrusted.
<<<
RATIONALE: >>>
L1: weft adds trust without its own communication (docs/14 §2). A read-only stick must work.
<<<
SATISFIES: SYS-020, SYS-021

[REQUIREMENT]
UID: AGT-012
STATUS: Active
VERIFICATION: Test
TITLE: Persistent documents
STATEMENT: >>>
Every document the agent holds shall be stored in a content-addressed directory before the decider sees it, and loaded on start, so that an offline device keeps its decisions across reboots.
<<<
RATIONALE: >>>
Without the documents, the verifier withholds components whose accepted documents are missing (fail safe); on an offline device nobody would bring them back.
<<<
SATISFIES: SYS-020, SYS-013

[REQUIREMENT]
UID: AGT-013
STATUS: Active
VERIFICATION: Test
TITLE: Outbox report
STATEMENT: >>>
After every round the agent shall write a report (installed, applied, executed and failed actions, conflicts, withheld components, rejected, pending and quarantined documents) atomically to an outbox directory. Quarantined documents stay listed after the round that rejected them.
<<<
RATIONALE: >>>
Reported state in weft terms, independent of how it travels (SYS-008); the adopter's tools read JSON.
<<<
SATISFIES: SYS-008, SYS-011

[REQUIREMENT]
UID: AGT-014
STATUS: Active
VERIFICATION: Test
TITLE: Config files
STATEMENT: >>>
The executor shall write the effective configuration of a component atomically as JSON to the config directory, at a path derived from the component name that cannot leave that directory, and then run the optional config hook.
<<<
RATIONALE: >>>
Services read plain files; a component name from a document must never become a path outside the config directory.
<<<
SATISFIES: SYS-003

[REQUIREMENT]
UID: AGT-015
STATUS: Active
VERIFICATION: Test
TITLE: Install hook
STATEMENT: >>>
The executor shall install an artifact by running the configured install hook with the component and the artifact digest in environment variables, never interpolated into the command; a failing or missing hook is reported, not recorded as installed, and retried.
<<<
RATIONALE: >>>
L1 keeps the adopter's own OTA tool; values from documents must not become shell code.
<<<
SATISFIES: SYS-003

[REQUIREMENT]
UID: AGT-016
STATUS: Active
VERIFICATION: Test
TITLE: Executed results survive restarts
STATEMENT: >>>
What is installed and applied shall be saved after each round and loaded on start, so a reboot does not repeat installs. Delivery to hooks is at least once.
<<<
RATIONALE: >>>
A crash between a hook and the save repeats the hook; hooks must be idempotent.
<<<
SATISFIES: SYS-006

[REQUIREMENT]
UID: AGT-017
STATUS: Active
VERIFICATION: Test
TITLE: Typed executor protocol
STATEMENT: >>>
The executor shall accept only two typed requests over its socket (apply configuration, install an artifact), as bounded, deterministic CBOR frames; it shall refuse anything else, re-check that a configuration matches its hash and that a component name is a safe path, and keep serving after malformed input.
<<<
RATIONALE: >>>
The privileged process parses almost nothing and cannot be asked for arbitrary actions (docs/07 §2, docs/20 §1).
<<<
SATISFIES: SYS-003, SYS-016

[REQUIREMENT]
UID: AGT-018
STATUS: Active
VERIFICATION: Test
TITLE: Separated, unprivileged decider
STATEMENT: >>>
The decider shall be able to run as its own process without privileges, without network and on a read-only system, and shall not be able to name commands, hooks or directories for the executor; those are configured on the executor's side only.
<<<
RATIONALE: >>>
A flaw in the code that parses untrusted documents yields a sandboxed process that can only request verified actions. Sandboxing: dist/systemd/weft-decider.service.
<<<
SATISFIES: SYS-003

[REQUIREMENT]
UID: AGT-019
STATUS: Active
VERIFICATION: Test
TITLE: Executor outages are safe
STATEMENT: >>>
If the executor is unreachable or fails, the instruction shall be reported as failed, not recorded as executed, and retried in a later round.
<<<
RATIONALE: >>>
Restarts of either process must not lose or duplicate recorded results.
<<<
SATISFIES: SYS-006, SYS-008

[[/SECTION]]
